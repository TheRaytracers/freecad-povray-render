import xml.etree.ElementTree as xml
import hashlib

def getNodes(node,tagChain):
    tagChain += node.tag
    nodes = node.getchildren()
    for subnode in nodes:
        getNodes(subnode,tagChain)
        if subnode.tag.lower() == "predef":
            hash1 = hashlib.sha1(tagChain.encode("UTF-8")).hexdigest()
            hash2 = hashlib.sha1(subnode.text.encode("UTF-8")).hexdigest()
            hashComplete = hash1[:4] + hash2[:4]
            try:
                uid = subnode.attrib['uid']
            except:
                subnode.set("uid",hashComplete)
            App.Console.PrintMessage(hashComplete + " - " + tagChain + " - " + subnode.text  + "\n")
    return tagChain

#main

MacroPath = App.ParamGet("User parameter:BaseApp/Preferences/Macro").GetString('MacroPath') #get macro path
predefinedPath = MacroPath + "/predefined.xml"

tree = xml.parse(predefinedPath)
predefined = tree.getroot()
getNodes(predefined,"")

outputFile = MacroPath + "/predefinedNew.xml"
tree.write(outputFile)
